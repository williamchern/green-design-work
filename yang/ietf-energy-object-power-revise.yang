module ietf-energy-object-power {
  yang-version 1.1;
  
  namespace "urn:ietf:params:xml:ns:yang:ietf-energy-object-power";
  prefix eo;
  
  import ietf-hardware {
    prefix hw;
    reference
      "RFC 8348: A YANG Data Model for Hardware Management";
  }
  
  import ietf-inet-types {
    prefix inet;
    reference
      "RFC 6991: Common YANG Data Types";
  }
  

  organization
    "IETF GREEN Working Group";
  
  contact
    "WG Web: <https://datatracker.ietf.org/wg/green/>
     WG List: <mailto:green@ietf.org>";
     
     
  
  description
    "This YANG module defines the data model for energy object power
     attributes, translated from the eoPowerTable in RFC7460.
     
     Copyright (c) 2025 IETF Trust and the persons identified as
     authors of the code. All rights reserved.
     
     Redistribution and use in source and binary forms, with or
     without modification, is permitted pursuant to, and subject to
     the license terms contained in, the Simplified BSD License set
     forth in Section 4.c of the IETF Trust's Legal Provisions
     Relating to IETF Documents
     (https://trustee.ietf.org/license-info).
     
     This version of this YANG module is part of RFC XXXX
     (https://www.rfc-editor.org/info/rfcXXXX); see the RFC itself
     for full legal notices.";
  
  revision 2025-11-27 {
    description
      "Initial revision";
    reference
      "RFC XXXX: Energy Object YANG Data Model";
  }
  
  identity data-accuracy {
    description
      "Base identity for all possible data accuracy types.
       This identity serves as the root for a hierarchy of accuracy
       types, allowing for extensibility while maintaining alignment
       with current and future industry standards.

       The hierarchy, as defined in this YANG module, is as follows.
       Other modules may extend this hierarchy with additional
       accuracy base- and sub-types as needed.

       data-accuracy
        ├── accuracy-unknown
        │    └── accuracy-unavailable
        ├── accuracy-estimated
        │    ├── accuracy-static
        │    ├── accuracy-historic
        │    ├── accuracy-learned
        └── accuracy-measured
             ├── accuracy-measured-bronze
             ├── accuracy-measured-silver
             ├── accuracy-measured-gold
             ├── accuracy-measured-red
             └── accuracy-measured-ones
      ";
  }
  identity accuracy-unknown {
    base data-accuracy;
    description
      "The accuracy of the power data is unknown.";
  }
  identity accuracy-unavailable {
    base data-accuracy-unknown;
    description
      "A power data is not available for some reason, such
        as a sensor failure or a component being powered off.";
  }
  identity accuracy-estimated {
    base data-accuracy;
    description
      "The power data is estimated, perhaps based on a model,
       history or calculation rather than a direct measurement.";
  }
  identity accuracy-static {
    base accuracy-estimated;
    description
      "The power data is based on static data, such as
       manufacturer specifications, datasheet of typical power values
       or nameplate ratings, rather than real-time measurements.";
  }
  identity accuracy-historic {
    base accuracy-estimated;
    description
      "The power data is based on an historic measurement data
       for this specific system and usage pattern.";
  }
  identity accuracy-learned {
    base accuracy-estimated;
    description
      "The power data is based on an machine learning
       model prediction.";
  }
  identity accuracy-measured {
    base data-accuracy;
    description
      "The power data is a direct, real-time measurement
       from a sensor.";
  }
  identity accuracy-measured-bronze {
    base accuracy-measured;
    description
      "The power data is a direct, real-time measurement
       from a sensor with +/- 30% accuracy for typical values.";
  }
  identity accuracy-measured-silver {
    base accuracy-measured;
    description
      "The power data is a direct, real-time measurement
       from a sensor with +/- 10% accuracy for typical values.";
  }  
  identity accuracy-measured-gold {
    base accuracy-measured;
    description
      "The power data is a direct, real-time measurement
       from a sensor with +/- 5% accuracy for typical values.";
  }
  identity accuracy-measured-red {
    base accuracy-measured;
    description
      "The power data is a direct, real-time measurement
       from a sensor with +/- 2% accuracy for typical values.";
  }
  identity accuracy-measured-ones {
    base accuracy-measured;
    description
      "The power data is a direct, real-time measurement
       from a sensor with all non-zero digits valid.";
  }
  
  typedef power-factor {
    type uint8 {
      range "0 .. 100";
    }
    default 100;
    description
      "The percent value of the power factor measurement.
       Leaf often omitted, implying 100%.";
    reference
      "Replaces RFC 7460: eoPowerCurrentType object";
  }

  identity power-state {
    description
      "Base identity for all possible power states. This identity
       serves as the root for a hierarchy of power states, allowing
       for extensibility while maintaining alignment with the IANA
       Power State Set Registry.";
    reference
      "IANA: Power State Set Registry";
  }

  identity unit-multiplier {
    description 
      "Base identity for unit multipliers as defined in IEC 61850-7-3
       Annex A. These represent exponents of 10 for scaling units 
       associated with the integer units used to measure the power or 
       energy.";
    reference
      "RFC 7460: UnitMultiplier";
  }

  identity multiplier-milli {
    description 
      "Represents a multiplier of 10^-3 (0.001) associated with the 
       integer units used to measure the power or energy.";
    reference
      "RFC 7460: UnitMultiplier";
  }

  identity multiplier-none {
    description 
      "Represents a multiplier of 1 (no multiplier) associated with 
       the integer units used to measure the power or energy.";
    reference
      "RFC 7460: UnitMultiplier";
  }

  identity multiplier-kilo {
    description 
      "Represents a multiplier of 10^3 (1,000) associated with the 
       integer units used to measure the power or energy.";
    reference
      "RFC 7460: UnitMultiplier";
  }

  identity multiplier-mega {
    description
      "Represents a multiplier of 10^6 (1,000,000) associated with 
       the integer units used to measure the power or energy.";
    reference
      "RFC 7460: UnitMultiplier";
  }

  identity multiplier-giga {
    description 
      "Represents a multiplier of 10^9 (1,000,000,000) associated 
       with the integer units used to measure the power or energy.";
    reference
      "RFC 7460: UnitMultiplier";
  }

  container energy-objects {
    description
      "Energy objects container for power attributes.";
    reference
      "RFC 7460: eoPowerTable";
    
    list power-entry {
      key "object-id";
      description
        "Power entry for an energy object, indexed by object id.
         Each entry contains the complete set of power attributes
         for a specific physical component.";
      reference
        "RFC 7460: EoPowerEntry";
        
      leaf object-id {
        type string;
        description
          "An identifier that uniquely identifies the energy object in
           a device.";
      }        
      
      leaf source-component-id {
        type leafref {
          path "/hw:hardware/hw:component/hw:name";
        }
        description
          "Reference to the component name in the ietf-hardware model.
           This leaf creates a direct semantic link between the power 
           attributes and the physical component they describe.";
      }
            
      leaf eo-power {
        type int32;
        units "Watts";
        description
          "The current power usage measurement for the energy object.
           This value represents the instantaneous power consumption
           of the component. Positive values indicate power consumption,
           while negative values can indicate power generation (e.g., for
           devices with battery backup or renewable energy sources).";
        reference
          "RFC 7460: eoPower object";
      }
      
      leaf eo-power-nameplate {
        type uint32;
        units "Watts";
        description
          "The nameplate power rating of an energy object. This is the
           maximum power that the device is designed to consume or
           produce, as specified by the manufacturer. Essential for
           power budget calculations and capacity planning.";
        reference
          "RFC 7460: eoPowerNameplate object";
      }
      
      leaf eo-power-unit-multiplier {
        type identityref {
          base unit-multiplier;
        }
        description
          "The unit multiplier used to measure the power or energy. This 
           multiplier applies to both eo-power and eo-power-nameplate 
           values, allowing representation of power values from milliwatts 
           to gigawatts using integer arithmetic.";
        reference
          "RFC 7460: eoPowerUnitMultiplier object";
      }
      
      leaf eo-power-accuracy {
        type int32;
        units "Percentage";
        description
          "The presumed accuracy of the power measurement, expressed as
           a percentage. Positive values indicate the degree of accuracy,
           while negative values might indicate specific error conditions.
           This value helps management applications assess the reliability
           of the power data.";
        reference
          "RFC 7460: eoPowerAccuracy object";
      }
      
      leaf eo-power-measurement-provenance {
        type measurement-provenance;
        description
          "The provenance of the power measurement. Indicates whether the
           value is a direct measurement, an estimate, or unavailable.
           This metadata is crucial for network management applications
           to assess the reliability and accuracy of the power data.";
        reference
          "RFC 7460: eoPowerMeasurementCaliber object";
      }
      
      leaf eo-power-power-factor {
        type power-factor;
        description
          "The percent value of the power factor measurement for the 
          energy object. This information is important for understanding 
          the electrical characteristics of the device and for correctly 
          interpreting the power data.";
        reference
          "Replaces RFC 7460: eoPowerCurrentType object";
      }
      
      leaf eo-power-measurement-local {
        type boolean;
        description
          "Indicates whether the power measurement is local (true) or
           remote (false). A local measurement is taken directly at the
           device, while a remote measurement is collected from an external
           source. This information can be useful for troubleshooting and
           understanding the data source.";
        reference
          "RFC 7460: eoPowerMeasurementLocal object";
      }
      
      leaf eo-power-admin-state {
        type identityref {
          base power-state;
        }
        description
          "The administratively desired power state for the energy object.
           This is the power state that a management application wants the
           device to be in. The actual operational state may differ due to
           automatic power management, thermal constraints, or other factors.
           This leaf is read-write, allowing management applications to
           control the power state of components.";
        reference
          "RFC 7460: eoPowerAdminState object";
      }
      
      leaf eo-power-oper-state {
        type identityref {
          base power-state;
        }
        config false;
        description
          "The current operational power state of the energy object.
           This is the actual power state that the device is currently in,
           which may differ from the administrative state if, for example,
           a power-saving feature has automatically changed the state.
           This leaf is read-only, as its value is determined by the device.";
        reference
          "RFC 7460: eoPowerOperState object";
      }
      
      leaf eo-power-state-enter-reason {
        type string;
        description
          "A textual description of the reason why the energy object
           entered its current power state. This information is valuable
           for troubleshooting, auditing, and understanding the behavior
           of the device's power management features. Examples include
           'user command', 'automatic power-saving', or 'thermal protection activated'.";
        reference
          "RFC 7460: eoPowerStateEnterReason object";
      }
    }
  }
}
