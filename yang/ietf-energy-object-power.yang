module ietf-energy-object-power {
  yang-version 1.1;
  
  namespace "urn:ietf:params:xml:ns:yang:ietf-energy-object-power";
  prefix eo;
  
  import ietf-hardware {
    prefix hw;
    reference
      "RFC 8348: A YANG Data Model for Hardware Management";
  }
  
  import ietf-inet-types {
    prefix inet;
    reference
      "RFC 6991: Common YANG Data Types";
  }
  

  organization
    "IETF GREEN Working Group";
  
  contact
    "WG Web: <https://datatracker.ietf.org/wg/green/>
     WG List: <mailto:green@ietf.org>";
     
     Editor:   
     
  
  description
    "This YANG module defines the data model for energy object power
     attributes, translated from the eoPowerTable in RFC7460.
     
     Copyright (c) 2025 IETF Trust and the persons identified as
     authors of the code. All rights reserved.
     
     Redistribution and use in source and binary forms, with or
     without modification, is permitted pursuant to, and subject to
     the license terms contained in, the Simplified BSD License set
     forth in Section 4.c of the IETF Trust's Legal Provisions
     Relating to IETF Documents
     (https://trustee.ietf.org/license-info).
     
     This version of this YANG module is part of RFC XXXX
     (https://www.rfc-editor.org/info/rfcXXXX); see the RFC itself
     for full legal notices.";
  
  revision 2025-11-13 {
    description
      "Initial revision";
    reference
      "RFC XXXX: Energy Object YANG Data Model";
  }
  
  typedef unit-multiplier {
    type enumeration {
      enum milli {
        value -3;
        description
          "Represents a multiplier of 10^-3 (0.001)";
      }
      enum none {
        value 0;
        description
          "Represents a multiplier of 1 (no multiplier)";
      }
      enum kilo {
        value 3;
        description
          "Represents a multiplier of 10^3 (1,000)";
      }
      enum mega {
        value 6;
        description
          "Represents a multiplier of 10^6 (1,000,000)";
      }
      enum giga {
        value 9;
        description
          "Represents a multiplier of 10^9 (1,000,000,000)";
      }
    }
    description
      "An integer value that represents the IEEE 61850 Annex A units
       multiplier associated with the integer units used to measure
       the power or energy.";
    reference
      "RFC 7460: UnitMultiplier textual convention";
  }
  
  typedef measurement-caliber {
    type enumeration {
      enum unknown {
        description
          "The caliber of the power measurement is unknown.";
      }
      enum estimated {
        description
          "The power measurement is estimated, perhaps based on a
           model or calculation rather than a direct measurement.";
      }
      enum measured {
        description
          "The power measurement is a direct, real-time measurement
           from a sensor.";
      }
      enum unavailable {
        description
          "A power measurement is not available for some reason, such
           as a sensor failure or a component being powered off.";
      }
    }
    description
      "The caliber of the power measurement.";
    reference
      "RFC 7460: eoPowerMeasurementCaliber object";
  }
  
  typedef current-type {
    type enumeration {
      enum unknown {
        description
          "The current type is not known.";
      }
      enum ac {
        description
          "The measurement is for an Alternating Current (AC) power
           source.";
      }
      enum dc {
        description
          "The measurement is for a Direct Current (DC) power source.";
      }
    }
    description
      "The type of electrical current (AC or DC) for the energy object.";
    reference
      "RFC 7460: eoPowerCurrentType object";
  }
  
  identity power-state {
    description
      "Base identity for all possible power states. This identity
       serves as the root for a hierarchy of power states, allowing
       for extensibility while maintaining alignment with the IANA
       Power State Set Registry.";
    reference
      "IANA: Power State Set Registry";
  }
  
  container energy-objects {
    description
      "Energy objects container for power attributes.";
    reference
      "RFC 7460: eoPowerTable";
    
    list power-entry {
      key "object-id";
      description
        "Power entry for an energy object, indexed by object id.
         Each entry contains the complete set of power attributes
         for a specific physical component.";
      reference
        "RFC 7460: EoPowerEntry";
        
        leaf object-id {
          type string;
          description
            "An identifier that uniquely identifies the energy object in
             a device.";
        }        
      
      leaf source-component-id {
        type leafref {
          path "/hw:hardware/hw:component/hw:name";
        }
        description
          "Reference to the component name in the ietf-hardware model.
           This leaf creates a direct semantic link between the power 
           attributes and the physical component they describe.";
      }
      
      
      leaf eo-power {
        type int32;
        units "Watts";
        description
          "The current power usage measurement for the energy object.
           This value represents the instantaneous power consumption
           of the component. Positive values indicate power consumption,
           while negative values can indicate power generation (e.g., for
           devices with battery backup or renewable energy sources).";
        reference
          "RFC 7460: eoPower object";
      }
      
      leaf eo-power-nameplate {
        type uint32;
        units "Watts";
        description
          "The nameplate power rating of an energy object. This is the
           maximum power that the device is designed to consume or
           produce, as specified by the manufacturer. Essential for
           power budget calculations and capacity planning.";
        reference
          "RFC 7460: eoPowerNameplate object";
      }
      
      leaf eo-power-unit-multiplier {
        type unit-multiplier;
        description
          "The unit multiplier associated with the integer units used to
           measure the power or energy. This multiplier applies to both
           eo-power and eo-power-nameplate values, allowing representation
           of power values from milliwatts to gigawatts using integer
           arithmetic.";
        reference
          "RFC 7460: eoPowerUnitMultiplier object";
      }
      
      leaf eo-power-accuracy {
        type int32;
        units "Percentage";
        description
          "The presumed accuracy of the power measurement, expressed as
           a percentage. Positive values indicate the degree of accuracy,
           while negative values might indicate specific error conditions.
           This value helps management applications assess the reliability
           of the power data.";
        reference
          "RFC 7460: eoPowerAccuracy object";
      }
      
      leaf eo-power-measurement-caliber {
        type measurement-caliber;
        description
          "The caliber of the power measurement. Indicates whether the
           value is a direct measurement, an estimate, or unavailable.
           This metadata is crucial for network management applications
           to assess the reliability and accuracy of the power data.";
        reference
          "RFC 7460: eoPowerMeasurementCaliber object";
      }
      
      leaf eo-power-current-type {
        type current-type;
        description
          "The type of electrical current (AC or DC) for the energy object.
           This information is important for understanding the electrical
           characteristics of the device and for correctly interpreting
           the power data.";
        reference
          "RFC 7460: eoPowerCurrentType object";
      }
      
      leaf eo-power-measurement-local {
        type boolean;
        description
          "Indicates whether the power measurement is local (true) or
           remote (false). A local measurement is taken directly at the
           device, while a remote measurement is collected from an external
           source. This information can be useful for troubleshooting and
           understanding the data source.";
        reference
          "RFC 7460: eoPowerMeasurementLocal object";
      }
      
      leaf eo-power-admin-state {
        type identityref {
          base power-state;
        }
        description
          "The administratively desired power state for the energy object.
           This is the power state that a management application wants the
           device to be in. The actual operational state may differ due to
           automatic power management, thermal constraints, or other factors.
           This leaf is read-write, allowing management applications to
           control the power state of components.";
        reference
          "RFC 7460: eoPowerAdminState object";
      }
      
      leaf eo-power-oper-state {
        type identityref {
          base power-state;
        }
        config false;
        description
          "The current operational power state of the energy object.
           This is the actual power state that the device is currently in,
           which may differ from the administrative state if, for example,
           a power-saving feature has automatically changed the state.
           This leaf is read-only, as its value is determined by the device.";
        reference
          "RFC 7460: eoPowerOperState object";
      }
      
      leaf eo-power-state-enter-reason {
        type string;
        description
          "A textual description of the reason why the energy object
           entered its current power state. This information is valuable
           for troubleshooting, auditing, and understanding the behavior
           of the device's power management features. Examples include
           'user command', 'automatic power-saving', or 'thermal protection activated'.";
        reference
          "RFC 7460: eoPowerStateEnterReason object";
      }
    }
  }
}
