module ietf-power-and-energy {
  yang-version 1.1;
  
  namespace "urn:ietf:params:xml:ns:yang:ietf-power-and-energy";
  prefix eo;
  
  import ietf-hardware {
    prefix hw;
    reference
      "RFC 8348: A YANG Data Model for Hardware Management";
  }
  
  import ietf-iana-power-and-energy {
    prefix ianaeo;
    reference
      "IANA-defined identities for power and energy class";
  }

  organization
    "IETF GREEN Working Group";
  
  contact
    "WG Web: <https://datatracker.ietf.org/wg/green/>
     WG List: <mailto:green@ietf.org>";
     
     
  
  description
    "This YANG module specifies for Power and Energy monitoring and 
     control of devices within or connected to communication 
     networks.
     
     Copyright (c) 2025 IETF Trust and the persons identified as
     authors of the code. All rights reserved.
     
     Redistribution and use in source and binary forms, with or
     without modification, is permitted pursuant to, and subject to
     the license terms contained in, the Simplified BSD License set
     forth in Section 4.c of the IETF Trust's Legal Provisions
     Relating to IETF Documents
     (https://trustee.ietf.org/license-info).
     
     This version of this YANG module is part of RFC XXXX
     (https://www.rfc-editor.org/info/rfcXXXX); see the RFC itself
     for full legal notices.";
  
  revision 2026-01-22 {
    description
      "Initial revision";
    reference
      "RFC XXXX: Energy Object YANG Data Model";
  }
  
  identity data-source-accuracy {
    description
      "Base identity for all possible data accuracy types.
       This identity serves as the root for a hierarchy of accuracy
       types, allowing for extensibility while maintaining alignment
       with current and future industry standards.

       The hierarchy, as defined in this YANG module, is as follows.
       Other modules may extend this hierarchy with additional
       accuracy base- and sub-types as needed.

       data-source-accuracy
        ├── accuracy-like-parent
        ├── accuracy-unknown
        │    └── accuracy-unavailable
        ├── accuracy-estimated
        │    ├── accuracy-static
        │    ├── accuracy-historic
        │    └── accuracy-learned
        └── accuracy-measured
             ├── accuracy-measured-bronze
             │    ├── accuracy-measured-bronze-1
             │    ├── accuracy-measured-bronze-10
             │    ├── accuracy-measured-bronze-100
             │    └── accuracy-measured-bronze-1000
             ├── accuracy-measured-silver
             │    └── accuracy-measured-silver-...
             ├── accuracy-measured-gold
             │    └── accuracy-measured-gold-...
             ├── accuracy-measured-red
             │    └── accuracy-measured-red-...
             └── accuracy-measured-ones

       The accuracy levels under accuracy-measured are based on
       percent-wise accuracy classes:
          bronze:  +/- 30%
          silver:  +/- 10%
          gold:    +/- 5%
          red:     +/- 2%

       In addition, the accuracy-measured-ones identity indicates
       a power data measurement with all digits valid, except trailing
       zeros.

       Since percent-wise accuracy works poorly for very small
       values, standards such as IEC 62053, IEC 61850-7-4 and
       IEEE 1451 define accuracy classes based on a combination of
       percent-wise accuracy and absolute accuracy thresholds.
       E.g. +/-1 % of reading  +  +/-0.05 absolute units.

       Similarly, for each percent-wise accuracy class, this module
       defines a few absolute tolerance classes, indicated by
       suffixes to the accuracy identity names. The suffixes indicate
       absolute accuracy thresholds:
          no suffix:   +/-0.5  absolute units
          -1:          +/-1    absolute unit
          -10:         +/-10   absolute units
          -100:        +/-100  absolute units
          -1000:       +/-1000 absolute units
       Thus, for example, accuracy-measured-gold-10 indicates
       a power data measurement with an accuracy of either
       +/-5% or +/-10 absolute units, whichever is larger.

       For example, a power sensor reading might report a value
       of 16250, with unit multiplier of milli (10^-3), under
       accuracy-measured-gold-10. This indicates that the actual
       power value is between 16.2375 and 16.2625 Watts, since
       5% of 16.250 Watts is 0.8125 Watts, which is greater than
       the absolute threshold of 10 milliwatts (0.010 W).

       At another time, the same sensor might report a value
       of 150, with unit multiplier of milli (10^-3), under
       accuracy-measured-gold-10. This indicates that the actual
       power value is between 0.140 and 0.160 Watts, since 5% of 
       0.150 Watts is only 0.0075 Watts, which is less than the
       absolute threshold of 10 milliwatts (0.010 W).";
  }
  identity accuracy-unknown {
    base data-source-accuracy;
    description
      "The accuracy of the power data is unknown.";
  }
  identity accuracy-unavailable {
    base accuracy-unknown;
    description
      "A power data is not available for some reason, such
       as a sensor failure or a component being powered off.";
  }
  identity accuracy-like-parent {
    base data-source-accuracy;
    description
      "The accuracy of the power/energy data is the same as this energy
       object's parent object. This identity is useful for hierarchical
       energy objects where child objects inherit the accuracy
       characteristics.";
  }
  identity accuracy-estimated {
    base data-source-accuracy;
    description
      "The power data is estimated, perhaps based on a model,
       history or calculation rather than a direct measurement.";
  }
  identity accuracy-static {
    base accuracy-estimated;
    description
      "The power data is based on static data, such as
       manufacturer specifications, datasheet of typical power values
       or nameplate ratings, rather than real-time measurements.";
  }
  identity accuracy-historic {
    base accuracy-estimated;
    description
      "The power data is based on an historic measurement data
       for this specific system and usage pattern.";
  }
  identity accuracy-learned {
    base accuracy-estimated;
    description
      "The power data is based on an machine learning
       model prediction.";
  }
  identity accuracy-measured {
    base data-source-accuracy;
    description
      "The power data is a direct, real-time measurement
       from a sensor.";
  }
  identity accuracy-measured-bronze {
    base accuracy-measured;
    description
      "The power data is a direct, real-time measurement
       from a sensor with precision and accuracy such that
        |actual-sensor| ≤ sensor * 30% OR |actual-sensor| ≤ 0.5";
  }
  identity accuracy-measured-bronze-1 {
    base accuracy-measured-bronze;
    description
      "The power data is a direct, real-time measurement
       from a sensor with precision and accuracy such that
       |actual-sensor| ≤ sensor * 30% OR |actual-sensor| ≤ 1";
  }  
  identity accuracy-measured-bronze-10 {
    base accuracy-measured-bronze;
    description
      "The power data is a direct, real-time measurement
       from a sensor with precision and accuracy such that
       |actual-sensor| ≤ sensor * 30% OR |actual-sensor| ≤ 10";
  }  
  identity accuracy-measured-bronze-100 {
    base accuracy-measured-bronze;
    description
      "The power data is a direct, real-time measurement
       from a sensor with precision and accuracy such that
       |actual-sensor| ≤ sensor * 30% OR |actual-sensor| ≤ 100";
  }  
  identity accuracy-measured-bronze-1000 {
    base accuracy-measured-bronze;
    description
      "The power data is a direct, real-time measurement
       from a sensor with precision and accuracy such that
       |actual-sensor| ≤ sensor * 30% OR |actual-sensor| ≤ 1000";
  }  
  identity accuracy-measured-silver {
    base accuracy-measured;
    description
      "The power data is a direct, real-time measurement
       from a sensor with precision and accuracy such that
        |actual-sensor| ≤ sensor * 10% OR |actual-sensor| ≤ 0.5";
  }  
  identity accuracy-measured-silver-1 {
    base accuracy-measured-silver;
    description
      "The power data is a direct, real-time measurement
       from a sensor with precision and accuracy such that
       |actual-sensor| ≤ sensor * 10% OR |actual-sensor| ≤ 1";
  }  
  identity accuracy-measured-silver-10 {
    base accuracy-measured-silver;
    description
      "The power data is a direct, real-time measurement
       from a sensor with precision and accuracy such that
       |actual-sensor| ≤ sensor * 10% OR |actual-sensor| ≤ 10";
  }  
  identity accuracy-measured-silver-100 {
    base accuracy-measured-silver;
    description
      "The power data is a direct, real-time measurement
       from a sensor with precision and accuracy such that
       |actual-sensor| ≤ sensor * 10% OR |actual-sensor| ≤ 100  ";
  }  
  identity accuracy-measured-silver-1000 {
    base accuracy-measured-silver;
    description
      "The power data is a direct, real-time measurement
       from a sensor with precision and accuracy such that
       |actual-sensor| ≤ sensor * 10% OR |actual-sensor| ≤ 1000";
  }  
  identity accuracy-measured-gold {
    base accuracy-measured;
    description
      "The power data is a direct, real-time measurement
       from a sensor with precision and accuracy such that
       |actual-sensor| ≤ sensor * 5% OR |actual-sensor| ≤ 0.5";
  }
  identity accuracy-measured-gold-1 {
    base accuracy-measured-gold;
    description
      "The power data is a direct, real-time measurement
       from a sensor with precision and accuracy such that
       |actual-sensor| ≤ sensor * 5% OR |actual-sensor| ≤ 1";
  }  
  identity accuracy-measured-gold-10 {
    base accuracy-measured-gold;
    description
      "The power data is a direct, real-time measurement
       from a sensor with precision and accuracy such that
       |actual-sensor| ≤ sensor * 5% OR |actual-sensor| ≤ 10";
  }  
  identity accuracy-measured-gold-100 {
    base accuracy-measured-gold;
    description
      "The power data is a direct, real-time measurement
       from a sensor with precision and accuracy such that
       |actual-sensor| ≤ sensor * 5% OR |actual-sensor| ≤ 100";
  }  
  identity accuracy-measured-gold-1000 {
    base accuracy-measured-gold;
    description
      "The power data is a direct, real-time measurement
       from a sensor with precision and accuracy such that
       |actual-sensor| ≤ sensor * 5% OR |actual-sensor| ≤ 1000";
  }  
  identity accuracy-measured-red {
    base accuracy-measured;
    description
      "The power data is a direct, real-time measurement
       from a sensor with precision and accuracy such that
       |actual-sensor| ≤ sensor * 2% OR |actual-sensor| ≤ 0.5";
  }
  identity accuracy-measured-red-1 {
    base accuracy-measured-red;
    description
      "The power data is a direct, real-time measurement
       from a sensor with precision and accuracy such that
       |actual-sensor| ≤ sensor * 2% OR |actual-sensor| ≤ 1";
  }  
  identity accuracy-measured-red-10 {
    base accuracy-measured-red;
    description
      "The power data is a direct, real-time measurement
       from a sensor with precision and accuracy such that
       |actual-sensor| ≤ sensor * 2% OR |actual-sensor| ≤ 10";
  }  
  identity accuracy-measured-red-100 {
    base accuracy-measured-red;
    description
      "The power data is a direct, real-time measurement
       from a sensor with precision and accuracy such that
       |actual-sensor| ≤ sensor * 2% OR |actual-sensor| ≤ 100";
  }  
  identity accuracy-measured-red-1000 {
    base accuracy-measured-red;
    description
      "The power data is a direct, real-time measurement
       from a sensor with precision and accuracy such that
       |actual-sensor| ≤ sensor * 2% OR |actual-sensor| ≤ 1000";
  }  
  identity accuracy-measured-ones {
    base accuracy-measured;
    description
      "The power data is a direct, real-time measurement
       from a sensor with all digits valid, except trailing zeros.
       For example, a sensor reading of 12300 represents
       a sensor value between 12250 and 12350.";
  }
  
  typedef power-factor {
    type uint8 {
      range "0 .. 100";
    }
    default 100;
    description
      "The percent value of the power factor measurement.
       Leaf often omitted, implying 100%.";
    reference
      "Replaces RFC 7460: eoPowerCurrentType object";
  }

  identity power-state {
    description
      "Base identity for all possible power states. This identity
       serves as the root for a hierarchy of power states, allowing
       for extensibility while maintaining alignment with the IANA
       Power State Set Registry.";
    reference
      "IANA: Power State Set Registry";
  }
  identity power-state-admin {
    base power-state;
    description
      "Base identity for administratively requested power states. The 
       administrative power state indicates the desired power state 
       requested for the Energy Object by a management system.";
    reference
      "RFC 7460: Section 5.3 (Power State)";
  }
  identity power-state-oper {
    base power-state;
    description
      "Base identity for operational power states. The operational 
       power state indicates the actual current power state of the 
       Energy Object. A difference between the administrative state 
       and the operational state indicates that the Energy Object is 
       transitioning between power states.";
    reference
      "RFC 7460: Section 5.3 (Power State)";
  }
  identity power-state-enter-reason {
    description
      "Base identity for reasons why an Energy Object entered its 
       current operational power state. This is analogous to the 
       enumeration values defined for eoPowerStateEnterReason 
       in RFC 7460.";
    reference
      "RFC 7460: eoPowerStateEnterReason";
  }
  identity power-state-on {
    base power-state;
    description "full power on.";
    reference
      "RFC 7460: PowerStateSet";
  }
  identity power-state-off {
    base power-state;
    description "power off.";
    reference
      "RFC 7460: PowerStateSet";
  }
  identity unit-multiplier {
    description 
      "Base identity for unit multipliers as defined in IEC 61850-7-3
       Annex A. These represent exponents of 10 for scaling units 
       associated with the integer units used to measure the power or 
       energy.
           yocto(-24),   -- 10^-24
           zepto(-21),   -- 10^-21
           atto(-18),    -- 10^-18
           femto(-15),   -- 10^-15
           pico(-12),    -- 10^-12
           nano(-9),     -- 10^-9
           micro(-6),    -- 10^-6
           milli(-3),    -- 10^-3
           units(0),     -- 10^0
           kilo(3),      -- 10^3
           mega(6),      -- 10^6
           giga(9),      -- 10^9
           tera(12),     -- 10^12
           peta(15),     -- 10^15
           exa(18),      -- 10^18
           zetta(21),    -- 10^21
           yotta(24)     -- 10^24
        ";
    reference
      "RFC 7460: UnitMultiplier";
  }
  identity multiplier-yocto {
    description 
      "Represents a multiplier of 10^-24 associated with the
       integer units used to measure the power or energy.";
  }
  identity multiplier-zepto {
    description 
      "Represents a multiplier of 10^-21 associated with the 
       integer units used to measure the power or energy.";
  }
  identity multiplier-atto {
    description 
      "Represents a multiplier of 10^-18 associated with the 
       integer units used to measure the power or energy.";
  }
  identity multiplier-femto {
    description 
      "Represents a multiplier of 10^-15 associated with the 
       integer units used to measure the power or energy.";
  }
  identity multiplier-pico {
    description 
      "Represents a multiplier of 10^-12 associated with the 
       integer units used to measure the power or energy.";
  }
  identity multiplier-nano {
    description 
      "Represents a multiplier of 10^-9 associated with the 
       integer units used to measure the power or energy.";
  }
  identity multiplier-micro {
    description 
      "Represents a multiplier of 10^-6 (0.000001) associated with the
       integer units used to measure the power or energy.";
  }
  identity multiplier-milli {
    description 
      "Represents a multiplier of 10^-3 (0.001) associated with the 
       integer units used to measure the power or energy.";
  }
  identity multiplier-units {
    description 
      "Represents a multiplier of 10^0 (1) associated with 
       the integer units used to measure the power or energy.";
  }
  identity multiplier-kilo {
    description 
      "Represents a multiplier of 10^3 (1,000) associated with the 
       integer units used to measure the power or energy.";
    reference
      "RFC 7460: UnitMultiplier";
  }
  identity multiplier-mega {
    description
      "Represents a multiplier of 10^6 (1,000,000) associated with 
       the integer units used to measure the power or energy.";
  }
  identity multiplier-giga {
    description 
      "Represents a multiplier of 10^9 (1,000,000,000) associated 
       with the integer units used to measure the power or energy.";
  }
  identity multiplier-tera {
    description
      "Represents a multiplier of 10^12 associated 
       with the integer units used to measure the power or energy.";
  }
  identity multiplier-peta {
    description
      "Represents a multiplier of 10^15 associated 
       with the integer units used to measure the power or energy.";
  }
  identity multiplier-exa {
    description
      "Represents a multiplier of 10^18 associated 
       with the integer units used to measure the power or energy.";
  }
  identity multiplier-zetta {
    description
      "Represents a multiplier of 10^21 associated 
       with the integer units used to measure the power or energy.";
  }
  identity multiplier-yotta {
    description
      "Represents a multiplier of 10^24 associated 
       with the integer units used to measure the power or energy.";
  }
  identity energy-relationship-type {
    description "Base identity for energy object relationships";
    reference "RFC 7461: IANAEnergyRelationship";
  }
  identity powered-by {
    base energy-relationship-type;
    description "Energy Object A is powered by Energy Object B";
  }
  identity powering {
    base energy-relationship-type;
    description "Energy Object A is powering Energy Object B";
  }
  identity metered-by {
    base energy-relationship-type;
    description "Energy Object A is metered by Energy Object B";
  }
  identity metering {
    base energy-relationship-type;
    description "Energy Object A is metering Energy Object B";
  }
  identity aggregated-by {
    base energy-relationship-type;
    description "Energy Object A is aggregated by Energy Object B";
  }
  identity aggregating {
    base energy-relationship-type;
    description "Energy Object A is aggregating Energy Object B";
  }

  container energy-objects {
    config false;
    description
      "Energy objects container for power and energy attributes.";
    reference
      "RFC 7460: eoPowerTable, eoEnergyTable";
    
    list energy-entry {
      key "object-id";
      description
        "Power and energy entry for an energy object, indexed by object id.
         Each entry contains the complete set of power and energy attributes
         for a specific physical component.";
      reference
        "RFC 7460: eoPowerEntry, eoEnergyTable";
        
      leaf object-id {
        type string;
        description
          "An identifier that uniquely identifies the energy object 
          in an energy object.";
      }
      
      leaf source-component-id {
        type leafref {
          path "/hw:hardware/hw:component/hw:name";
        }
        description
          "Reference to the component name in the ietf-hardware 
          model. This leaf creates a direct semantic link between the
          power/energy attributes and the physical component they describe.
          ";
      }

      container power {
        description
          "Container for power measurement attributes.";
        reference
          "RFC 7460: eoPowerEntry attributes";
        leaf instantaneous-power {
          type int32;
          units "Watts";
          mandatory true;
          description
            "The power usage measurement for the energy object right now.
            This value represents the instantaneous power consumption
            of the component. This value is specified in SI units of watts 
            with the magnitude of watts (milliwatts, kilowatts, etc.) indicated 
            separately as unit-multiplier in this container. Positive values 
            indicate power consumption, while negative values can indicate power 
            generation (e.g., for devices with battery backup or 
            renewable energy sources).";
          reference
            "RFC 7460: eoPower object";
        }
        
        leaf nameplate-power {
          type uint32;
          units "Watts";
          description
            "The nameplate power rating of an energy object. This is 
            the maximum power that the energy object is designed to consume or
            produce, as specified by the manufacturer. Essential for
            power budget calculations and capacity planning.";
          reference
            "RFC 7460: eoPowerNameplate object";
        }
        
        leaf unit-multiplier {
          type identityref {
            base unit-multiplier;
          }
          mandatory true;
          description
            "The unit multiplier used to measure the power. 
            This multiplier applies to both instantaneous-power and nameplate-power
            values, allowing representation of power values from milliwatts
            to gigawatts using integer arithmetic.";
          reference
            "RFC 7460: eoPowerUnitMultiplier object";
        }
        
        leaf data-source-accuracy {
          type identityref {
            base data-source-accuracy;
          }
          default accuracy-like-parent;
          description
            "The accuracy of the power data source. Indicates whether 
            the data source is a direct measurement, an estimate, or 
            unavailable and also the accuracy level of the data source. 
            By default, the accuracy is inherited from the parent energy
            object, facilitating hierarchical accuracy definitions
            without the need to specify accuracy at every level.
            This metadata is crucial for network management 
            applications to assess the reliability and accuracy of the 
            power data.";
          reference
            "RFC 7460: eoPowerMeasurementCaliber object";
        }
        
        leaf power-factor {
          type power-factor;
          description
            "The percent value of the power factor measurement for the 
            energy object. This information is important for 
            understanding the electrical characteristics of the energy object
            and for correctly interpreting the power data.";
          reference
            "Replaces RFC 7460: eoPowerCurrentType object";
        }

        leaf measurement-local {
          type boolean;
          description
            "Indicates whether the power measurement is local (true) or
             remote (false). A local measurement is taken directly at
             the energy object, while a remote measurement is collected from
             an external source. This information can be useful for
             troubleshooting and understanding the data source.";
           reference
             "RFC 7460: eoPowerMeasurementLocal object";
        }
      }

      container energy {
        description
          "Container for energy measurement attributes.";
        reference
          "RFC 7460: eoEnergyEntry attributes";
        
        leaf total-energy-consumed {
          type uint64;
          units "Watt-hours";
          description
            "The total cumulative energy consumed by the energy object
            since the last reset. This value is specified as 
            watt-hours with the magnitude of watt-hours (milliwatt-hours, 
            kilowatt-hours, etc.) indicated separately as unit-multiplier 
            in this container. This value is useful for tracking
            overall energy usage over time for billing, reporting,
            or optimization purposes.";
          reference
            "RFC 7460: eoEnergyConsumed object";
        }
        
        leaf total-energy-delivered {
          type uint64;
          units "Watt-hours";
          description
            "The total cumulative energy delivered by the energy object
            since the last reset. This value is specified as
            watt-hours with the magnitude of watt-hours (milliwatt-hours, 
            kilowatt-hours, etc.) indicated separately as unit-multiplier 
            in this container. This value is relevant for energy objects
            capable of generating power, such as those with renewable
            energy sources or battery backup systems, or capable of providing
            energy to other energy objects (e.g., PoE switches).";
          reference
            "RFC 7460: eoEnergyProduced object";
        }
        leaf unit-multiplier {
          type identityref {
            base unit-multiplier;
          }
          description
            "This multiplier applies to both total-energy-consumed
             and total-energy-delivered values. It determines the scale
             of the energy measurements, allowing representation of
             energy values from milliwatt-hours to gigawatt-hours
             using integer arithmetic.";
          reference
            "RFC 7460: eoPowerUnitMultiplier object";
        }
        
        leaf data-source-accuracy {
          type identityref {
            base data-source-accuracy;
          }
          default accuracy-like-parent;
          description
            "The accuracy of the energy data source. Indicates whether 
            the data source is a direct measurement, an estimate, or 
            unavailable and also the accuracy level of the data source. 
            By default, the accuracy is inherited from the parent energy
            object, facilitating hierarchical accuracy definitions
            without the need to specify accuracy at every level.
            This metadata is crucial for network management 
            applications to assess the reliability and accuracy of the 
            energy data.";
          reference
            "RFC 7460: eoPowerMeasurementCaliber object";
        }
        leaf measurement-local {
          type boolean;
          description
            "Indicates whether the energy measurement is local (true) or
             remote (false). A local measurement is taken directly at
             the energy object, while a remote measurement is collected from
             an external source. This information can be useful for
             troubleshooting and understanding the data source.";
           reference
             "RFC 7460: eoPowerMeasurementLocal object";
        }
        leaf-list certifications {
          type identityref {
            base ianaeo:certification-type;
          }
          description
            "List of certifications applicable to this energy object. If 
            this list is empty, the energy object has no certifications.";
        }    
      }
      container power-state {
        description
          "Container for Power state monitoring.";
        leaf power-state-oper {
          type identityref {
            base power-state-oper;
          }
          description
            "The actual operational power state of the Energy Object.
             This reflects the current state, which may differ from the
             admin-state during transitions.";
          reference
            "RFC 7460: eoPowerOperState";
        }
      }

      list relationship {
        config false;
        key "type";
        description "Relationships for this energy entry. Replaces 
        RFC 7461 eoRelationTable.";
        reference
          "RFC 7461: eoRelationTable, eoRelationEntry";
                
        leaf type {
          type identityref {
            base energy-relationship-type; 
            // powered-by, powering, metered-by, metering, etc.
          }
          description
            "The type of relationship this energy object has with peer 
            objects.";
          reference
            "RFC 7461: eoRelationship, IANAEnergyRelationship";
        }
        
        list peer {
          key "id";
          description "Multiple peers for this relationship type.";
          reference
            "RFC 7461: eoRelationID";
          
          leaf id {
            type string;
            description "This id specifies the Universally Unique
              Identifier (UUID) of the peer (other) Energy Object that
              this energy object is powering/powered-by/metering/
              metered-by, etc. If the network level UUID is not known,
              some other locally unique identifier MAY be used, in
              conjunction with a human readable details.";
            reference
              "RFC 7461: eoRelationID (UUIDorZero)";
          }
          leaf details {
            type string;
            description 
              "Human-readable details of the peer relationship.
               Useful when network level UUID of the peer is not
               known.";
          }
        }
      }
    }
  }
  
  container energy-control {
    description
      "Energy control configuration, mirroring monitored objects.";
    reference
      "RFC 7460: eoPowerTable";
    list energy-entry {
      key "object-id";
      description
        "Control entry for a specific energy object.";
      reference
        "RFC 7460: eoPowerEntry";
      leaf object-id {
        type string;
        description "Must match an existing energy-object object-id.";
        must "/energy-objects/energy-entry[object-id=current()]" {
          error-message "The referenced object-id does not exist in 
                         energy-objects.";
        }
      }
      container power-state {
        description
          "Container for Power state management and monitoring.";
        leaf power-state-admin {
          type identityref {
            base power-state-admin;
          }
          description
            "The administratively requested power state for the 
             Energy Object. This is the state that the management 
             system desires the energy object to be in.";
          reference
            "RFC 7460: eoPowerAdminState";
        }
        leaf state-enter-reason {
          type identityref {
            base power-state-enter-reason;
          }
          description
            "The reason why the Energy Object entered its current 
             operational power state. This is set whenever the 
             power-state-oper changes.";
          reference
            "RFC 7460: eoPowerStateEnterReason";
        }
      }
    }
  }
}
